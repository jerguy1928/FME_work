FME workspace CSV_cleaning_and_converting.fmw

Parameters:
- DestDataset_SHAPEFILE_5 = /Users/jeremyherbert/Downloads/new-york-city-airbnb-open-data   # Destination Esri Shapefile Folder
- DestDataset_SHAPEFILE = /Users/jeremyherbert/Downloads/new-york-city-airbnb-open-data   # Destination Esri Shapefile Folder
- DestDataset_SHAPEFILE_4 = /Users/jeremyherbert/Downloads/new-york-city-airbnb-open-data   # Destination Esri Shapefile Folder
- SourceDataset_CSV2_3 = https://raw.githubusercontent.com/jerguy1928/FME_work/master/AB_NYC_2019.csv   # Source CSV (Comma Separated Value) File(s)

Readers:
- CSV2_2: CSV2 from $(SourceDataset_CSV2_3)

Writers:
- SHAPEFILE_2: SHAPEFILE to $(DestDataset_SHAPEFILE_5)
- SHAPEFILE_1: SHAPEFILE to $(DestDataset_SHAPEFILE)
- SHAPEFILE_3: SHAPEFILE to $(DestDataset_SHAPEFILE_4)

CSV (reader CSV2_2)
    attributes: id uint32, name string, host_id uint32, host_name string, neighbourhood_group string, neighbourhood string, latitude y_coordinate, longitude x_coordinate, room_type string, price uint16, minimum_nights uint16, number_of_reviews uint16, last_review string, reviews_per_month real32, calculated_host_listings_count uint8, availability_365 uint16
    -> Price_Checker
Note: Ensure valid price (>0)
Price_Checker: Tester
    BOOL_OP = OR
    COMPOSITE_TEST = 1
    TEST_CLAUSE = TEST @Value(price) > 0
    TEST_MODE = TEST
    PASSED -> Minimum_Nights
Note: Looking for shorter term airbnbs (minimum stay 30 nights or less)
Minimum_Nights: Tester
    BOOL_OP = OR
    COMPOSITE_TEST = 1
    TEST_CLAUSE = TEST @Value(minimum_nights) <= 30
    TEST_MODE = TEST
    PASSED -> Remove_Duplicate_Places
Note: Looking for unique listings, / checking if any places have the same name and price (e.g. same room type in hotel)
Remove_Duplicate_Places: DuplicateFilter
    INPUT_ORDERED_CHOICE = No
    KEYATTR = name price
    UNIQUE -> Has_Reviews
Note: Place has received a review before
Has_Reviews: Tester
    BOOL_OP = OR
    COMPOSITE_TEST = 1
    TEST_CLAUSE = TEST @Value(number_of_reviews) > 0
    TEST_MODE = TEST
    PASSED -> Valid_Host_Name
Note: A host lists a valid name
Valid_Host_Name: Tester
    BOOL_OP = COMPOSITE
    COMPOSITE_TEST = 1 AND 2
    TEST_CLAUSE:
      TEST host_name NOT_ATTRIBUTE_IS_EMPTY ""
      TEST @Value(host_name) NOT_= (Email hidden by Airbnb)
    TEST_MODE = TEST
    PASSED -> AttributeManager
Note: Keeping useful attributes
AttributeManager
    ATTR_TABLE:
      RENAME_SET_VALUE id > Listing ID
      RENAME_SET_VALUE name > Listing Name
      RENAME_SET_VALUE neighbourhood_group > Borough
      RENAME_SET_VALUE neighbourhood > Neighborhood
      RENAME_SET_VALUE latitude > Latitude
      RENAME_SET_VALUE longitude > Longitude
      RENAME_SET_VALUE room_type > Type of Room
      RENAME_SET_VALUE price > Average price/night
      RENAME_SET_VALUE minimum_nights > Minimum Stay
      REMOVE number_of_reviews
      REMOVE last_review
      REMOVE reviews_per_month
      REMOVE calculated_host_listings_count
      REMOVE availability_365
      RENAME_SET_VALUE host_id > Host ID
      RENAME_SET_VALUE host_name > Host Name
    -> NYC Airbnb's with reviews (writer SHAPEFILE_3)
Note: Exporting Data to Shapefile
NYC Airbnb's with reviews (writer SHAPEFILE_3)
    attributes: Place_ID double, Place_Name char(254), Borough char(254), Area char(254), Room_Type char(254), USD_Night long, Min_Stay long, Host_ID double, Host_Name char(254), Latitude double, Longitude double
